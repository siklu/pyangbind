module radio-bridge-tg-radio-dn {

    yang-version "1";

    // namespace
    namespace "http://siklu.com/yang/tg/radio/dn";

    prefix rb-tg-radio-dn;
    import radio-bridge-tg-radio-common {
        prefix "rb-tg-radio";
        revision-date 2021-11-18;
    }
    import radio-bridge-tg-types {
        prefix "rb-tg-types";
        revision-date 2021-05-25;
    }

    // meta
    organization
      "Siklu";

    contact
      "Support: <https://siklu.com/contact/>";

    description
      "This YANG module is part of radio-bridge TG project.
        It defines the dn radio part of the project";

    revision 2021-11-25 {
        description
          "Removed ignore-gps added sync-mode";
        reference
          "";
    }

    revision 2021-11-18 {
        description
          "1.2.0 release";
        reference
          "";
    }

    revision 2021-05-25 {
        description
          "Release";
        reference
          "";
    }

    revision 2020-11-22 {
        description
          "Initial Revision";
        reference
          "";
    }

    // extension statements
    // feature statements
    // identity statements
    // typedef statements
    typedef dn-link-state-type {
        type enumeration {
            enum Connected {
                description
                  "The link is connected";
            }
            enum LinkAdminDown {
                description
                  "Link admin state is down";
            }
            enum SectorAdminDown {
                description
                  "Local sectors of the link are down";
            }
            enum WaitingUpstreamConnection {
                description
                  "Waiting for pop-dn";
            }
            enum WaitingInQueue {
                description
                  "Waiting in queue";
            }
            enum Ignition {
                description
                  "Link ignition in progress";
            }
        }
        description
          "Possible states of ignition. Items are ordered by displaying priority";
    }

    typedef dn-sync-mode-type {
        type enumeration {
            enum no-sync {
                description
                  "Allows link creation without GPS. This is practical for indoor link tests
                   or in places where there is no GPS connectivity. Without GPS the system can
                   create only 1 hop links.";
            }
            enum gps-sync {
                description
                  "Regular sync. RF links will drop when the unit will lose GPS sync.";
            }
            enum gps-sync-holdover {
                description
                  "RF links will not drop when the unit will lose GPS sync. This mode will be a
                   default sync mode for all N3XX devices.";
            }
            enum rf-sync {
                description
                  "The device will use the HTSF feature to synchronize all
                   RF sectors from the RF sync of the incoming RF link";
            }
        }
        description
          "Describes DN sync modes";
    }

    // grouping statements
    grouping node-dn-top {
        container node-config {
            description
              "The container includes all the configuration that are related to the entire TG unit.";
            container default-radio-profile {
                uses rb-tg-radio:radio-frequency;
                uses rb-tg-radio:radio-polarity;
                uses rb-tg-radio:radio-golay-index;
                description
                  "Defaults for radio configuration (Rx-Tx). Applies to sectors when they have no specified radio configuration.";
            }
            leaf is-pop-dn {
                type boolean;
                description
                  "Define this as a POP-DN or a regular Node";
            }
            leaf sync-mode {
                type dn-sync-mode-type;
                default gps-sync-holdover;
                description
                  "Specify how the node will synchronize with other nodes on the network";
            }
        }
        description
          "Grouping for node configuration and defaults";
    }
    grouping sectors-dn-top {
        container sectors-config {
            description
              "Contain all parameters for sectors.";
            list sector {
                key index;
                leaf index {
                    type rb-tg-types:radio-sector-index;
                    description
                      "The index of the sector.";
                }
                // container ssid-profile {
                // uses ssid-profile;
                // description
                // "SSID configuration. 
                // Must be configured if the respective parameters are unspecified in default-ssid-profile, otherwise overrides them.";
                // }
                container radio-profile {
                    uses rb-tg-radio:radio-frequency;
                    uses rb-tg-radio:radio-polarity;
                    uses rb-tg-radio:radio-golay-index;
                    description
                      "Radio configuration (Rx-Tx).
                        Must be configured if the respective parameters are unspecified in default-radio-profile, otherwise overrides them.";
                }
                description
                  "List of all sectors";
            }
        }
        description
          "Grouping for sectors configuration and default configuration data.";
    }

    grouping configured-link-top {
        description
          "Configuration for a link";
        leaf remote-assigned-name {
            type rb-tg-types:node-assigned-name;
            description
              "The netowrk assigned name/ID (AN) of the remote unit to which a link is defined.";
        }

        list remote-sector {
            key index;
            leaf index {
                type rb-tg-types:radio-sector-index;
                description
                  "The index of the sector";
            }
            // min-elements 1; // TODO(itziks): in the future we will not need to set remote sector if responder-node-type=cn (i.e. TU)
            description
              "A list of sectors on the remote unit, to which the link can be setup.";
        }

        list local-sector {
            key index; // TODO(itziks): index must exist in sectors list
            leaf index {
                type rb-tg-types:radio-sector-index;
                description
                  "The index of the sector";
            }
            // min-elements 1; // TODO(itziks)
            description
              "A list of sectors on the local unit, from which the link can be setup.";
        }

        leaf control-superframe {
            type rb-tg-radio:control-superframe;
            // TODO(itziks): enforce constraints based on responder-node-type (see description below)
            mandatory true;
            description
              "If responder-node-type = CN: must be set to unspecified.
               If responder-node-type = node/DN: can be either 0 or 1, but different between remote DNs on the same local sector 
               (can be max. 2 node-node links per sector)";
        }

        leaf responder-node-type {
            type rb-tg-radio:node-type;
            description
              "The requested node-type of the remote unit. The link will be rejected if the remote unit is already 
               configured to a different type by another active link";
        }

        leaf admin-status {
            type rb-tg-types:admin-status;
            default up;
            description
              "Defines whether to initiate the link (and keep it up) or drop it (in case it was already established)";
        }

        leaf tx-power-control {
            type rb-tg-radio:tx-power-control-type;
            description
              "lock txPower to 6, 31, auto for purpose of naive alignment";
        }
    }

    grouping dn-link-state {
        description
          "Contains information of ignition process";

        container state {
            leaf state {
                type dn-link-state-type;
                config false;
                description
                  "Explains state of ignition process";
            }
            uses rb-tg-radio:disconnected-link-state;
            description
              "Aggregates state and down-cause together";
        }
    }

    grouping golay-group {
        leaf tx-golay-index {
            type rb-tg-radio:golay-index;
            description
              "Tx Golay index of Golay code sequence";
        }
        leaf rx-golay-index {
            type rb-tg-radio:golay-index;
            description
              "Rx Golay index of Golay code sequence";
        }
        description
          "For overriding node/sector configuration from link";
    }

    grouping links-dn-top {
        container links {
            list configured {
                uses configured-link-top;
                uses dn-link-state;
                uses golay-group;
                key remote-assigned-name;

                description
                  "A list of all links that the node will try to initiate.";
            }
            description
              "Contains lists of all defined links in this node.";
        }
        description
          "Contains all links configuration";
    }

    grouping radio-dn-top {
        container radio-dn {
            description
              "Top level container for TG node radio";
            uses node-dn-top;
            uses sectors-dn-top;
            uses links-dn-top;
        }
        description
          "Top level grouping of radio data";
    }

    // data definition statements
    uses radio-dn-top;
// augment statements
// rpc statements
}
// notification statements

submodule subm-b {
  belongs-to mod-a { prefix a; }
  import mod-c { prefix "c"; }

  grouping TEST {
    leaf b {
      type c:t;
    }
  }

  container in-b { 
    leaf a { type string; }
  }

  identity i { }
  identity j { base i; }

}
